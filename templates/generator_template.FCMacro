# -*- coding: utf-8 -*-
"""
generator_template.FCMacro — CAD-as-Code skeleton
=================================================
Reads a YAML config, builds one part family, verifies, saves FCStd + STEP.

Run headless:
  /Applications/FreeCAD.app/Contents/Resources/bin/freecadcmd generator_template.FCMacro
  CONFIG=path/to/other.yaml freecadcmd generator_template.FCMacro
  EXPORT_DIR=exports freecadcmd generator_template.FCMacro   # also refresh curated exports

Outputs follow reference/output-convention.md:
  OUT_DIR/<family>/<SKU>/rNNN/{cad-manifest.json, <id>.FCStd, step/<id>-<part>.step}
  rNNN is reused when the config sha matches the existing manifest, else bumped.

FRAME: part axis = +Z, base disc bottom at Z=0, all dims mm.
"""
import os, re, zipfile, json, hashlib, datetime, glob, shutil
import FreeCAD as App
import Part
from FreeCAD import Vector

HERE = os.path.dirname(os.path.abspath(__file__))
CONFIG = os.environ.get("CONFIG", os.path.join(HERE, "config.example.yaml"))
OUT_DIR = os.environ.get("OUT_DIR", os.path.join(HERE, "output"))
EXPORT_DIR = os.environ.get("EXPORT_DIR", "")          # "" = don't refresh exports/
FAMILY = "arbor"
DOC_NAME = "Arbor"

def safe_relpath(path):
    """Path for manifests: relative to the generator's project dir when the
    file lives inside it, otherwise just the basename. Never let a manifest
    carry '..' hops or absolute paths from the machine that generated it."""
    root = os.path.abspath(os.path.dirname(HERE))
    ap = os.path.abspath(path)
    return os.path.relpath(ap, root) if ap.startswith(root + os.sep) else os.path.basename(ap)

def sha12(path):
    return hashlib.sha256(open(path, "rb").read()).hexdigest()[:12]

def allocate_rev(sku_dir, config_sha):
    """Reuse the rev whose manifest has this config_sha, else next rNNN."""
    os.makedirs(sku_dir, exist_ok=True)
    revs = sorted(d for d in os.listdir(sku_dir) if re.match(r"^r\d{3}$", d))
    for r in revs:
        m = os.path.join(sku_dir, r, "cad-manifest.json")
        try:
            if json.load(open(m)).get("config_sha") == config_sha:
                return os.path.join(sku_dir, r)
        except Exception:
            pass
    return os.path.join(sku_dir, "r%03d" % (len(revs) + 1))

# ---------------------------------------------------------------- config
def load_yaml(path):
    """Tiny tolerant YAML reader (scalars + one level of nesting). Use PyYAML
    if available; this keeps the template dependency-free under freecadcmd."""
    try:
        import yaml
        return yaml.safe_load(open(path))
    except Exception:
        pass
    cfg, section = {}, None
    for line in open(path):
        line = line.split("#", 1)[0].rstrip()
        if not line.strip():
            continue
        m = re.match(r"^(\s*)([A-Za-z_][\w]*):\s*(.*)$", line)
        if not m:
            continue
        indent, key, val = len(m.group(1)), m.group(2), m.group(3).strip()
        if indent == 0 and val == "":
            section = key; cfg[section] = {}; continue
        target = cfg[section] if indent and section else cfg
        try:
            val = float(val) if re.match(r"^-?[0-9.]+$", val) else val.strip('"\'')
        except ValueError:
            pass
        target[key] = val
    return cfg

# ---------------------------------------------------------------- build
def build_arbor(cfg):
    a = cfg["arbor"]
    bore = cfg["inner_diameter"]
    od = bore - a["fit_clr"]
    z = 0.0
    solid = Part.makeCylinder(a["base_disc_dia"] / 2, a["base_disc_t"], Vector(0, 0, z))
    z += a["base_disc_t"]
    lip = Part.makeCylinder((bore + a["seat_lip_dia"]) / 2, a["seat_t"], Vector(0, 0, z))
    z += a["seat_t"]
    body = Part.makeCylinder(od / 2, cfg["stack_length"], Vector(0, 0, z))
    z += cfg["stack_length"]
    solid = solid.fuse(lip).fuse(body).removeSplitter()
    hole = Part.makeCylinder(a["center_screw"] / 2, z + 2, Vector(0, 0, -1))
    solid = solid.cut(hole)
    return solid, dict(arbor_od=od, height=z, hole=hole)

# ---------------------------------------------------------------- verify
def verify(solid, info, cfg):
    ok = True
    res = info["hole"].common(solid).Volume
    print("  hole residual        %.4f mm^3" % res); ok &= res < 1e-6
    exp = 3.14159265 * (info["arbor_od"] / 2) ** 2 * cfg["stack_length"]
    print("  arbor OD             %.3f (bore %.2f - clr)" % (info["arbor_od"], cfg["inner_diameter"]))
    print("  volume               %.0f mm^3 (body alone ~%.0f)" % (solid.Volume, exp)); ok &= solid.Volume > exp
    print("  is solid / valid     %s / %s" % (bool(solid.Solids), solid.isValid())); ok &= bool(solid.Solids) and solid.isValid()
    return ok

# ---------------------------------------------------------------- save
def write_gui_visibility(fcstd, names):
    vps = "".join('<ViewProvider name="%s" expanded="0"><Properties Count="1" TransientCount="0">'
                  '<Property name="Visibility" type="App::PropertyBool"><Bool value="true"/>'
                  '</Property></Properties></ViewProvider>' % n for n in names)
    xml = ("<?xml version='1.0' encoding='utf-8'?>\n<Document SchemaVersion=\"1\">"
           "<ViewProviderData Count=\"%d\">%s</ViewProviderData></Document>\n" % (len(names), vps))
    with zipfile.ZipFile(fcstd, "a") as z:
        if "GuiDocument.xml" not in z.namelist():
            z.writestr("GuiDocument.xml", xml)

def main():
    cfg = load_yaml(CONFIG)
    sku = str(cfg.get("name", "default"))
    ident = "%s-%s" % (FAMILY, sku)
    config_sha = sha12(CONFIG)
    rev_dir = allocate_rev(os.path.join(OUT_DIR, FAMILY, sku), config_sha)
    step_dir = os.path.join(rev_dir, "step"); os.makedirs(step_dir, exist_ok=True)

    doc = App.getDocument(DOC_NAME) if DOC_NAME in App.listDocuments() else App.newDocument(DOC_NAME)
    for o in list(doc.Objects):
        doc.removeObject(o.Name)
    solid, info = build_arbor(cfg)
    part = "arbor_L%g" % cfg["stack_length"]
    obj = doc.addObject("Part::Feature", "%s_%s" % (sku, part)); obj.Shape = solid; obj.Visibility = True
    doc.recompute()
    print("%s (%s):" % (ident, os.path.relpath(rev_dir)))
    ok = verify(solid, info, cfg)
    for o in doc.Objects: o.purgeTouched()

    fcstd = os.path.join(rev_dir, ident + ".FCStd"); doc.saveAs(fcstd)
    if not App.GuiUp: write_gui_visibility(fcstd, [o.Name for o in doc.Objects])
    step = os.path.join(step_dir, "%s-%s.step" % (ident, part)); solid.exportStep(step)
    back = Part.read(step)
    dv = abs(back.Volume - solid.Volume)
    print("  STEP round-trip      solids=%d dV=%.4f" % (len(back.Solids), dv))
    result = "PASS" if ok and back.Solids else "FAIL"

    manifest = {
        "format": "cad-manifest", "schemaVersion": 1,
        "design": "%s@%s" % (ident, config_sha),
        "config_sha": config_sha, "config_path": safe_relpath(CONFIG),
        "generator": "%s@%s" % (os.path.basename(__file__), sha12(__file__)),
        "units": "mm",
        "params": {"arbor_od": round(info["arbor_od"], 3), "height": round(info["height"], 3),
                   "stack_length": cfg["stack_length"], "bore": cfg["inner_diameter"]},
        "parts": {part: {"file": os.path.relpath(step, rev_dir), "volume_mm3": round(solid.Volume)}},
        "checks": {"hole_residual": round(info["hole"].common(solid).Volume, 6),
                   "step_roundtrip_dV": round(dv, 6), "result": result},
        "generated_at": datetime.datetime.now(datetime.timezone.utc).strftime("%Y-%m-%dT%H:%M:%SZ"),
    }
    json.dump(manifest, open(os.path.join(rev_dir, "cad-manifest.json"), "w"), indent=2)

    if EXPORT_DIR:   # curated, committed copy of the latest STEPs + manifest
        dst = os.path.join(EXPORT_DIR, FAMILY); os.makedirs(dst, exist_ok=True)
        for f in glob.glob(os.path.join(step_dir, "*.step")):
            shutil.copy2(f, dst)
        shutil.copy2(os.path.join(rev_dir, "cad-manifest.json"), os.path.join(dst, ident + ".manifest.json"))
        print("  exported -> %s" % dst)
    print("RESULT %s -> %s" % (result, os.path.relpath(rev_dir)))

main()
